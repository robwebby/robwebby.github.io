FME workspace webapp.downloadresults.fmw

Parameters:
- SourceDataset_ACAD = $(FME_MF_DIR)Data\bad_data.dwg   # Source Autodesk AutoCAD DWG/DXF File(s)
- DestDataset_HTML = tester.html   # HTML Files(*.html)|*.html Destination Html File

Readers:
- ACAD_1: ACAD from $(SourceDataset_ACAD) in EPSG:2277

Writers:
- HTML_1: HTML to $(DestDataset_HTML)

water_distribution_lines (reader ACAD_1)
    attributes: ANNO_DIAM char(4), COMPKEY number(2,0), COMPTYPE number(2,0), DIAMETER number(3,0), DRAW number(2,0), FEATURE_ID char(25), LEAD_MAIN_ number(3,0), MATERIAL char(8), PROJECT char(9), PR_ZONE char(4), STATUS char(3), SYMCODE number(4,0), SYMCODE2 number(4,0), TILE char(4), WNM_TYPE char(8), YEAR_INSTA number(5,0)
    -> GeometryFilter
GeometryFilter
    BREAK_AGG = No
    GEOM_PORT_NAMES = Line
    LINE -> GeometryValidator
HTMLReportGenerator
    CONTENT_LIST = HTML
    PAGE_CONFIG = HTML{{HTML;<!DOCTYPE html> <html> <head>   <meta charset="utf-8">    <!-- Use the .htaccess and remove these lines to avoid edge case issues. More info: h5bp.com/i/378 -->   <meta http-equiv="X-UA-Compatible" content="IE=edge,chrome=1">    <title>Data validation failure</title>   <meta name="description" content="">    <!-- Mobile viewport optimized: h5bp.com/viewport -->   <meta name="viewport" content="width=device-width">    <!-- CSS goes in the document HEAD or added to your external stylesheet -->     <style type="text/css">     /* ------------------      styling for the tables         ------------------   */     body {         font-family: 'Lucida Sans Unicode', 'Lucida Grande', Sans-Serif;     }     table {       line-height: 1.6em;       font-size: 12px;       background: #fff;       margin: 45px;       width: 480px;       border-collapse: collapse;       text-align: left;     }          th {       font-size: 14px;       font-weight: normal;       color: #039;       padding: 10px 8px;       border-bottom: 2px solid #6678b1;     }          tr {       color: #669;       padding: 9px 8px 0px 8px;     }            </style>   </head> <body>  <h1>Validation FAILED</h1> @Value(_htmlTable)  </body> </html>;FME_CONTROLLER_QUERY_FILE;transformers/dependencies/html5/Custom HTML.fme}}
    TITLE = Failed
    -> HTML (writer HTML_1)
HTMLReportGenerator_2
    CONTENT_LIST = HEADER
    PAGE_CONFIG = HEADER{{TEXT;All data has passed the validation tests. ;HEADER;NO;ALIGNMENT;LEFT;COLOR;0,0,0;FME_CONTROLLER_QUERY_FILE;transformers\dependencies\html5\Header.fme}}
    TITLE = Good
    -> HTML (writer HTML_1)
HTML (writer HTML_1)
    attributes: html_content buffer

Bookmark: Validation
GeometryValidator
    ISSUE_ATTR_NAME = _issues
    OGC_SIMPLE_CHECK = OGC_SIMPLE_CHECK
    OGC_VALID_CHECK = OGC_VALID_CHECK
    PRESETS = OGC
    REPAIR = No
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%SELF_INTERSECTING_PARAMS%"Yes"%PLANAR_SURFACE%PLANAR_SURFACE_PARAMS%"Yes"%SHELL_VALIDATION%""%"Yes"%SOLID_VOID_REPAIR%""%"Yes"%OGC_SIMPLE_CHECK%""%"No"%OGC_VALID_CHECK%""%"No"%MISSING_TEXTURE_COORDINATES%""%"Yes"%MISSING_VERTEX_NORMALS%""%"Yes"
    PASSED -> Tester
    FAILED -> VariableSetter
VariableSetter
    SCOPE = Global
    VALUE = yes
    VARNAME = _invalidFeatures
    -> XMLTemplater_2 [ROOT]
XMLTemplater_2
    OUTPUT_XML_HEADER = No
    RESULT_ATTRIBUTE = Remarks
    ROOT_QUERY_EXPR:
      <div style="min-width: 200px;">Invalid Geometry
      </div>
    VISIBLE_QUERY_VALIDATE = No
    -> AttributeCreator
Tester
    BOOL_OP = OR
    TEST_CLAUSE = TEST @Value(DIAMETER) NOT_= 0
    FAILED -> VariableSetter_2
VariableSetter_2
    SCOPE = Global
    VALUE = yes
    VARNAME = _invalidFeatures
    -> XMLTemplater [ROOT]
XMLTemplater
    OUTPUT_XML_HEADER = No
    RESULT_ATTRIBUTE = Remarks
    ROOT_QUERY_EXPR:
      <div>Invalid Attribute: DIAMETER
      </div>
    VISIBLE_QUERY_VALIDATE = No
    -> AttributeCreator

Bookmark: Report creation
AttributeCreator
    ATTR_LIST = _invalid_features,yes
    -> GoogleStaticMapCreator
GoogleStaticMapCreator
    -> XMLTemplater_3 [ROW]
Creator
    GEOMTYPE = Geometry Object
    NUM = 1
    CREATED -> VariableRetriever_2
VariableRetriever_2
    SCOPE = Global
    VALUE_ATTR = _invalidFeatures
    VARNAME = _invalidFeatures
    -> Tester_3
Tester_3
    BOOL_OP = OR
    TEST_CLAUSE = TEST @Value(_invalidFeatures) = yes
    PASSED -> XMLTemplater_3 [ROOT]
XMLTemplater_3
    OUTPUT_XML_HEADER = No
    RESULT_ATTRIBUTE = _htmlTable
    ROOT_QUERY_EXPR:
      <table>
      <tr>
      <th>TILE</th>
      <th>FEATURE_ID</th>
      <th>DIAMETER</th>
      <th>WNM_TYPE</th>
      <th>Error Remarks</th>
      <th>Map</th>
      </tr>
      {fme:process-features("ROW")}
      </table>
    ROW_QUERY_EXPR:
      <tr>
      <td>{fme:get-attribute("TILE")}</td>
      <td>{fme:get-attribute("FEATURE_ID")}</td>
      <td>{fme:get-attribute("DIAMETER")}</td>
      <td>{fme:get-attribute("WNM_TYPE")}</td>
      <td>{fme:get-xml-attribute("Remarks")}</td>
      <td><img src='{fme:get-attribute("_StaticMapUrl")}'></img></td>
      </tr>
    VISIBLE_QUERY_VALIDATE = No
    -> NoFeaturesTester
NoFeaturesTester
    NOINPUT -> HTMLReportGenerator_2
    -> HTMLReportGenerator

FME custom transformer NoFeaturesTester
This transformer checks whether there are any input features. If not, then a single feature is ouput via the NOINPUT port. If INPUT features exist, then they are output via the INPUT output port.
Other transformers often generate features that signify an error condition. This transformer can be used to check for those features and if those features exists, then a separate action can be triggered.
    Example
This may be useful to test if any data emerges from a reader, when the 'Ignore Failed Readers' advanced parameter is set to yes.
Input Ports
    Input
Features to be checked for existence
    Output Ports
    NoInput
If no Input features exist, a single featue is returned via the NoInput port
    Output
Any feature that entered the Input port is returned via the Output port

INPUT (input)
    -> Sampler
    -> OUTPUT (output)
OUTPUT (output)
Sampler
    RATE = 1
    SAMPLE_MODE = No
    SAMPLE_TYPE_LONG = First N Features
    SAMPLED -> AttributeCreator_2
AttributeCreator_2
    ATTR_TABLE:
      SET_TO count = 0
      SET_TO remove = yes
    -> DuplicateFilter
Creator
    GEOMTYPE = Geometry Object
    NUM = 1
    CREATED -> AttributeCreator_3
AttributeCreator_3
    ATTR_TABLE = SET_TO no_features = true
    -> DuplicateFilter
DuplicateFilter
    INPUT_ORDERED_CHOICE = No
    KEYATTR = count
    UNIQUE -> Tester
Tester
    BOOL_OP = OR
    TEST_CLAUSE = TEST @Value(remove) != yes
    PASSED -> AttributeRemover
AttributeRemover
    REMOVE_ATTRS = count,remove
    -> NOINPUT (output)
NOINPUT (output)

FME custom transformer GoogleStaticMapCreator

Input (input)
    -> Reprojector
Reprojector
    DEST = EPSG:4326
    INTERPOLATION_TYPE_NAME = Nearest Neighbor
    RASTER_CELL_SIZE = Preserve Cells
    SOURCE = TX83-CF
    STROKE_ARCS = Yes
    REPROJECTED -> CoordinateSwapper
CoordinateSwapper
    SWAP_TYPE = X <-> Y
    -> GeometryExtractor
GeometryExtractor
    ATTR = _geometry
    KIND_LONG = OGC Well Known Text
    OGCVERSION = 1.1
    -> SubstringExtractor
SubstringExtractor
    END = -2
    RESULT_ATTR = _path
    SRC_ATTR = _geometry
    START = 12
    -> StringReplacer_2
StringReplacer_2
    CASE = no
    FIND_TEXT = ,
    NO_MATCH = _FME_NO_OP_
    REGEXP = no
    REPLACE_TEXT = |
    SRC_ATTRS = _path
    -> StringReplacer
StringReplacer
    CASE = no
    FIND_TEXT = " "
    NO_MATCH = _FME_NO_OP_
    REGEXP = no
    REPLACE_TEXT = ,
    SRC_ATTRS = _path
    -> CoordinateExtractor
CoordinateExtractor
    IND = 0
    X_ATTR = _x
    Y_ATTR = _y
    Z_ATTR = _z
    Z_DEFAULT = -9999
    -> StringConcatenator_5
StringConcatenator_5
    PARM_LINE = http://maps.googleapis.com/maps/api/staticmap?center=@Value(_x),@Value(_y)&amp&amp&size=200x200&amp&sensor=false&path=color:0x0000ff|weight:5|@Value(_path)&key=AIzaSyAAJ9HjDtsSOYUzLI6Xkvfc8RMHOi6RfIs
    VAL_ATTR = _StaticMapUrl
    -> Output (output)
Output (output)
